FME workspace 3_report_photo.fmw

Parameters:
- SourceDataset_TEXTLINE = $(FME_MF_DIR)photo-incoming.txt   # Source Text File(s)
- URL = https://demos-safe-software.fmecloud.com   # Web Connection URL
- HTTP_AUTH_USERNAME = demo-author   # Username
- HTTP_AUTH_PASSWORD =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   # Password
- PHOTO_MAP_URL = https://www.google.com/fusiontables/embedviz?q=select+col0+from+1r0xCHrPZYDQYAp5It8pUagWUcKUOzJr5bxjIs45C&viz=MAP&h=false&t=1&l=col0&y=2&tmplt=2&hml=KML   # Photo Map URL
- TOKEN = 8be243c0fc2f5f34977050bdab57ebbdd3e72aa2

Readers:
- TEXTLINE_1: TEXTLINE from $(SourceDataset_TEXTLINE)

Writers:
- GOOGLEFUSIONTABLES_1: GOOGLEFUSIONTABLES

text_line (reader TEXTLINE_1)
    attributes: text_line_data buffer
    -> JSONFlattener
URLBuilder: StringConcatenator
    PARM_LINE = $(URL)/fmerest/v2/resources/FME_SHAREDRESOURCE_DATA/filesys/Photos/@Value(random_photo_folder)/@Value(file_name_only)?accept=contents&token=$(TOKEN)&disposition=attachment
    VAL_ATTR = url_of_photo
    -> TimeStamper
    -> FMEServerEmailGenerator_2
    -> AttributeRenamer_2
AttributeRenamer_2
    ATTR_LIST = jpeg_exif_make,make,"",jpeg_exif_model,model,"",jpeg_exif_gpsaltitude,altitude,"",email_subject,subject,""
    -> VertexCreator
VertexCreator
    XVAL = @Value(longitude)
    MODE_NAME = Replace with Point
    YVAL = @Value(latitude)
    -> CoordinateSystemSetter
CoordinateSystemSetter
    COORDSYS = LL84
    -> PhotoOnMapPhotoLibrary (writer GOOGLEFUSIONTABLES_1)
Note: PhotoOnMapPhotoLibrary
PhotoOnMapPhotoLibrary (writer GOOGLEFUSIONTABLES_1)
    attributes: make text, model text, url_of_photo text, latitude number, longitude number, altitude number, subject text
HTTPMultipartUploader
    TARGET_URL = $(URL)/fmerest/v2/resources/FME_SHAREDRESOURCE_DATA/filesys/Photos/@Value(random_photo_folder)?createDirectories=true&detail=low&overwrite=false&token=$(TOKEN)
    TARGET_ATTR = _url_contents
    AUTH_METHOD = Basic
    RESPONSE_HEADER_LIST_ATTR = _headers
    UPLOAD_METHOD = POST
    PROXY_AUTH_METHOD = Basic
    ERROR_ATTR = _error
    USE_COOKIES = No
    MULTIPART_FORM_DATA_FILE = @Value(file_name_only) @Value(email_attachment)
    VERIFY_SSL_CERTIFICATES = Yes
    STATUS_CODE_ATTR = _http_status_code
    FOLLOW_REDIRECTS = Yes
    -> HTTPFileUploader_Output
    <REJECTED> -> HTTPFileUploader_Output
HTTPFileUploader_Output: Logger
    MAXFEATS = 20
    MAXCOORDS = 20
    MESSAGE = Feature is:

Bookmark: Flatten JSON to get all attributes
JSONFlattener
    RECURSIVE = Yes
    JSON_ATTR = text_line_data
    -> AttributeExposer_3
AttributeExposer_3
    ATTR_LIST = email_publisher_attachment{},email_publisher_to,email_publisher_received,email_publisher_subject,email_publisher_from,email_publisher_sent,email_publisher_content
    -> AttributeRenamer
AttributeRenamer
    ATTR_LIST = email_publisher_attachment{0},email_attachment,"",email_publisher_content,email_content,"",email_publisher_from,email_from,"",email_publisher_received,email_recieved,"",email_publisher_sent,email_sent,"",email_publisher_subject,email_subject,"",email_publisher_to,email_to,""
    -> FilenamePartExtractor

Bookmark: Grab the photo name
FilenamePartExtractor
    FILENAME_PART = Full Filename
    SRC_ATTR = email_attachment
    TGT_ATTR = file_name_only
    -> RasterReader_2
RasterReader_2
    DATASET = @Value(email_attachment)
    VISIBLE_READER_TYPE = JPEG (Joint Photographic Experts Group)
    CONTINUE_ON_READER_ERROR = No
    RASTER -> UUIDGenerator
UUIDGenerator
    UUID_ATTR = random_photo_folder
    -> AttributeExposer

Bookmark: Expose All Attributes from the Raster
AttributeExposer
    ATTR_LIST = jpeg_exif_make,jpeg_exif_model,jpeg_exif_gpslatitude,jpeg_exif_gpslatituderef,jpeg_exif_gpslongitude,jpeg_exif_gpslongituderef,jpeg_exif_aperturevalue,jpeg_exif_colorspace,jpeg_exif_componentsconfiguration,jpeg_exif_datetime,jpeg_exif_datetimedigitized,jpeg_exif_datetimeoriginal,jpeg_exif_exifversion,jpeg_exif_pixelxdimension,jpeg_exif_pixelydimension,jpeg_exif_software,jpeg_type,jpeg_exif_aperturevalue,jpeg_exif_exposuremode,jpeg_exif_exposureprogram,jpeg_exif_exposuretime,jpeg_exif_flash,jpeg_exif_flashpixversion,jpeg_exif_fnumber,jpeg_exif_focallength,jpeg_exif_focallengthin35mmfilm,jpeg_exif_gpsaltitude,jpeg_exif_gpsaltituderef,jpeg_exif_gpsimgdirection,jpeg_exif_gpsimgdirectionref,jpeg_exif_gpstimestamp,jpeg_exif_isospeedratings,jpeg_exif_meteringmode,jpeg_exif_orientation,jpeg_exif_resolutionunit,jpeg_exif_scenecapturetype,jpeg_exif_sensingmethod,jpeg_exif_sharpness,jpeg_exif_shutterspeedvalue,jpeg_exif_whitebalance,jpeg_exif_xresolution,jpeg_exif_ycbcrpositioning,jpeg_exif_yresolution
    -> AttributeClassifier

Bookmark: is the photo Geotagged?
AttributeClassifier
    SRC_ATTR = jpeg_exif_gpslatitude
    CLASS = ASCII
    FAILED -> FMEServerEmailGenerator
    PASSED -> AttributeValueMapper

Bookmark: Trigger Failure Email to User
FMEServerEmailGenerator
    email_subject = Your request FAILED!
    email_subscriber_content = Your photo was taken by: @Value(jpeg_exif_make), @Value(jpeg_exif_model).  This service failed as it only accepts photos that are geotagged.
    email_to = @Value(email_from)
    -> FMEServerNotifier_4
FMEServerNotifier_4
    URL = $(URL)
    USERNAME = $(HTTP_AUTH_USERNAME)
    BODY = @Value(text_line_data)
    PASSWORD = $(HTTP_AUTH_PASSWORD)
    TOPIC = photo_map_report

Bookmark: Rotate Image If Needed
AttributeValueMapper
    DIRECTION = Forward (Source To Destination)
    DEFAULT_VALUE = 0
    LUT = 1,0,3,180,6,-90,8,90
    SRC = jpeg_exif_orientation
    VAL_ATTR = _rotation
    -> TestFilter
TestFilter
    DEFAULT_VALUE = <UNFILTERED>
    TEST_LIST = BOOL_OP,OR,COMPOSITE_TEST,<Unused>,TEST_CLAUSE,"TEST ""@Value(_rotation)"" != ""0""",Rotation Needed
    Rotation Needed -> Rotator_2
    <UNFILTERED> -> AttributeSplitter
Rotator_2
    YORIG = 0
    XORIG = 0
    ANGLE = @Value(_rotation)
    ROTATED -> RasterRotationApplier
RasterRotationApplier
    INTERPOLATION_TYPE_NAME = Bilinear
    -> RasterExtractor
RasterExtractor
    RASTER_FORMAT = JPEG (Joint Photographic Experts Group)
    RASTER_FORMAT_ATTR = _rasterFormatName
    RASTER_BLOB_ATTR = _rasterBlob
    -> AttributeCreator
AttributeCreator
    ATTR_LIST = email_attachment,$(FME_SHAREDRESOURCE_TEMP)@Value(file_name_only)
    -> AttributeFileWriter
AttributeFileWriter
    CHAR_ENCODING = fme-binary
    SOURCE_ATTR = _rasterBlob
    OVERWRITE_FILE = Overwrite file
    FILE_NAME = @Value(email_attachment)
    -> AttributeRemover
AttributeRemover
    REMOVE_ATTRS = _rasterBlob
    -> AttributeSplitter

Bookmark: Build Latitude
AttributeSplitter
    TRIM_OPTION = Both
    LIST_NAME = _latlist
    ATTR_NAME = jpeg_exif_gpslatitude
    DELIMITER = " "
    DROP_EMPTY_PARTS = No
    -> AttributeTrimmer
AttributeTrimmer
    SRC_ATTRS = _latlist{0},_latlist{1},_latlist{2}
    TRIM_CHARS = ()
    TRIM_TO_NONE = Yes
    TRIM_TYPE = Both
    -> AttributeCreator_2
AttributeCreator_2
    ATTR_LIST = latitude,@Evaluate(@Value(_latlist{0})+(@Value(_latlist{1})/60.0)+(@Value(_latlist{2})/3600.0))
    -> Tester
Tester
    BOOL_OP = OR
    TEST_CLAUSE = TEST "@Value(jpeg_exif_gpslatituderef)" != "N"
    TEST_MODE = Automatic
    TEST_DESCRIPTION = ""
    PASSED -> AttributeCreator_4
    FAILED -> AttributeSplitter_2
AttributeCreator_4
    ATTR_LIST = latitude,-@Value(latitude)
    -> AttributeSplitter_2

Bookmark: Build Longitude
AttributeSplitter_2
    TRIM_OPTION = Both
    LIST_NAME = _longlist
    ATTR_NAME = jpeg_exif_gpslongitude
    DELIMITER = " "
    DROP_EMPTY_PARTS = No
    -> AttributeTrimmer_2
AttributeTrimmer_2
    SRC_ATTRS = _longlist{0},_longlist{1},_longlist{2}
    TRIM_CHARS = ()
    TRIM_TO_NONE = Yes
    TRIM_TYPE = Both
    -> AttributeCreator_3
AttributeCreator_3
    ATTR_LIST = longitude,@Evaluate(@Value(_longlist{0})+(@Value(_longlist{1})/60.0)+(@Value(_longlist{2})/3600.0))
    -> Tester_2
Tester_2
    BOOL_OP = OR
    TEST_CLAUSE = TEST "@Value(jpeg_exif_gpslongituderef)" = "W"
    TEST_MODE = Automatic
    TEST_DESCRIPTION = ""
    PASSED -> AttributeCreator_5
    FAILED -> 2DPointReplacer
AttributeCreator_5
    ATTR_LIST = longitude,-@Value(longitude)
    -> 2DPointReplacer
2DPointReplacer
    XVALATTR = @Value(longitude)
    YVALATTR = @Value(latitude)
    POINT -> AttributeTrimmer_3

Bookmark: BuildAltitude
AttributeTrimmer_3
    SRC_ATTRS = jpeg_exif_gpsaltitude
    TRIM_CHARS = ()
    TRIM_TO_NONE = Yes
    TRIM_TYPE = Both
    -> URLBuilder
    -> HTTPMultipartUploader

Bookmark: Trigger Success Email to User
FMEServerEmailGenerator_2
    email_subject = Your request succeeded!
    email_subscriber_content:
      Thanks for submitting your photo to the demo system!<br>

      <p>Your photo has been added to the catalog. To see the photo on a map go <a href="$(PHOTO_MAP_URL)&lat=@Value(latitude)&lng=@Value(longitude)&z=13">here</a>. A red pin indicates a location of a photo. Click on that to see a thumbnail and a link to the complete photo.</p>
    email_to = @Value(email_from)
    -> FMEServerNotifier_2
FMEServerNotifier_2
    URL = $(URL)
    USERNAME = $(HTTP_AUTH_USERNAME)
    BODY = @Value(text_line_data)
    PASSWORD = $(HTTP_AUTH_PASSWORD)
    TOPIC = photo_map_report

Bookmark: Trigger Downstream Event - ems_new_data_logged
TimeStamper
    TIME_ATTR = datetime
    FMT = XML DateTime (^Y-^m-^dT^H:^M:^S)
    -> StringConcatenator_3
StringConcatenator_3
    PARM_LINE:
      {
      "report_type": "photo",
      "email_from": "@Value(email_from)",
      "url": "@Value(url_of_photo)",
      "latitude": "@Value(latitude)",
      "longitude": "@Value(longitude)",
      "datetime": "@Value(datetime)",
      "subject": "@Value(email_subject)",
      "content":"@Value(email_content)"
      }
    VAL_ATTR = email_content
    -> FMEServerNotifier
FMEServerNotifier
    URL = $(URL)
    USERNAME = $(HTTP_AUTH_USERNAME)
    BODY = @Value(email_content)
    PASSWORD = $(HTTP_AUTH_PASSWORD)
    TOPIC = photo_map_new_data_logged

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_to =   # To
- email_cc =   # CC
- email_from =   # From
- email_replyto =   # Reply to
- email_subject =   # Subject
- email_subscriber_content =   # Message
- email_attachment_paths =   # Attachments (comma separated)

INPUT (input)
    -> Counter
Counter
    DOMAIN = counter
    CNT_ATTR = _email_feature_id
    SCOPE = Local
    START = 0
    -> ParameterFetcher
ParameterFetcher
    ATTR_LIST = _email_from {$(email_from)} _email_replyto {$(email_replyto)} _email_attachment_paths {$(email_attachment_paths)} _email_cc {$(email_cc)}
    -> AttributeCreator
AttributeCreator
    NUM_PRIOR_FEATURES = 0
    NUM_SUBSEQUENT_FEATURES = 0
    ATTR_LIST = _email_to,$(email_to),_email_subject,$(email_subject),_email_subscriber_content,$(email_subscriber_content)
    -> JSONTemplater
JSONTemplater
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    CONSECUTIVE_GROUPS = No
    VISIBLE_QUERY_VALIDATE = Yes
    RESULT_ATTRIBUTE = text_line_data
    -> Tester
Tester
    BOOL_OP = OR
    TEST_CLAUSE = TEST _email_attachment_paths ATTRIBUTE_IS_EMPTY <Unused>
    TEST_MODE = Automatic
    TEST_DESCRIPTION = ""
    PASSED -> OUTPUT (output)
    FAILED -> AttributeSplitter
OUTPUT (output)

Bookmark: Add the attachments
AttributeSplitter
    TRIM_OPTION = Both
    LIST_NAME = _email_attachment_path_list
    ATTR_NAME = _email_attachment_paths
    DELIMITER = ,
    DROP_EMPTY_PARTS = No
    -> ListExploder
ListExploder
    MODE = List Elements and Original Attributes
    LIST_ATTR = _email_attachment_path_list{}
    INDEX_ATTR = _element_index
    LIST_FOUND -> StringConcatenator
StringConcatenator
    PARM_LINE = "email_attachment{@Value(_element_index)}": "@Value(_email_attachment_path_list)"
    VAL_ATTR = _email_attachment_json
    -> Aggregator
Aggregator
    ORDERED = No
    SEP = ,
    CONCAT_ATTRS = _email_attachment_json
    ACCUM_ATTRS_NAME = Yes
    MODE = Assemble One Level
    GROUP_BY = _email_feature_id
    AGGREGATE_TYPE = Homogeneous Collection (If Possible)
    AGGREGATE -> StringReplacer_2
StringReplacer_2
    SRC_ATTRS = _email_attachment_json
    NO_MATCH = _FME_NO_OP_
    FIND_TEXT = \
    REGEXP = no
    CASE = no
    REPLACE_TEXT = \\
    -> StringReplacer
StringReplacer
    SRC_ATTRS = text_line_data
    NO_MATCH = _FME_NO_OP_
    FIND_TEXT = }
    REGEXP = no
    CASE = no
    REPLACE_TEXT:
      ,
      @Value(_email_attachment_json)
      }
    -> OUTPUT (output)
