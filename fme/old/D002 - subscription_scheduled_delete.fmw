FME workspace D002 - subscription_scheduled_delete.fmw

Readers:
- GOOGLEFUSIONTABLES_DB_1: GOOGLEFUSIONTABLES_DB

Writers:
- GOOGLEFUSIONTABLES_1: GOOGLEFUSIONTABLES in LL-WGS84
- GOOGLEFUSIONTABLES_DB_2: GOOGLEFUSIONTABLES_DB in LL-WGS84

Note: EMSExpireSubscriptions
EMSExpireSubscriptions (reader GOOGLEFUSIONTABLES_DB_1)
    attributes: email text, enddate text, request_id text, request_time text, startdate text, twitter text, query_type text
    -> DateFormatter
DateFormatter
    DATE_ATTR = enddate
    FMT = FME Date (%Y%m%d)
    -> TimeStamper
TimeStamper
    FMT = FME Date (^Y^m^d)
    TIME_ATTR = current_date
    -> TestFilter
    -> Logger
TestFilter
    TEST_LIST = BOOL_OP,OR,COMPOSITE_TEST,<Unused>,TEST_CLAUSE,"TEST ""@Value(enddate)"" < ""@Value(current_date)""",SubscriptionExpired
    SubscriptionExpired -> EMSActiveSubscriptions (writer GOOGLEFUSIONTABLES_1)
    <UNFILTERED> -> Logger
    SubscriptionExpired -> EMSExpireSubscriptions (writer GOOGLEFUSIONTABLES_DB_2)
Note: EMSActiveSubscriptions
EMSActiveSubscriptions (writer GOOGLEFUSIONTABLES_1)
    attributes: email text, request_id text, request_time text, enddate text, startdate text, twitter text, query_type text
Note: EMSExpireSubscriptions
EMSExpireSubscriptions (writer GOOGLEFUSIONTABLES_DB_2)
    attributes: email text, enddate text, request_id text, request_time text, startdate text, twitter text, query_type text
Logger [off]
    MESSAGE = Feature is:
    MAXFEATS = 20
    MAXCOORDS = 20
