FME workspace D002 - report_web_form_bufferer.fmw

Parameters:
- SourceDataset_TEXTLINE = Z:\DonStuff\DemoData\2012Demos\PushNotification\Data\trafficAccident.txt   # Source Text File(s)
- DestDataset_TEXTLINE = C:\temp\bufferout.txt   # Destination Text File File
- bufferamount = 1000   # Buffer Amount

Readers:
- TEXTLINE_1: TEXTLINE from $(SourceDataset_TEXTLINE)

Writers:
- TEXTLINE_2: TEXTLINE to $(DestDataset_TEXTLINE)

text_line (reader TEXTLINE_1)
    attributes: text_line_data buffer
    -> GeometryReplacer
GeometryReplacer
    KIND_LONG = OGC Well Known Text
    ATTR = text_line_data
    SRS_AXIS_ORDER_DISPLAY = Automatic
    -> Reprojector
Reprojector
    DEST = TX83-C
    SOURCE = EPSG:4326
    RASTER_CELL_SIZE = Preserve Cells
    INTERPOLATION_TYPE_NAME = Nearest Neighbor
    STROKE_ARCS = Yes
    REPROJECTED -> Bufferer
Bufferer
    BUFFSTYLE = CAP_ROUND
    WIDTH = $(bufferamount)
    ANGLE = 22.5
    BUFFERED -> Reprojector_2
Reprojector_2
    DEST = EPSG:4326
    SOURCE = TX83-C
    RASTER_CELL_SIZE = Preserve Cells
    INTERPOLATION_TYPE_NAME = Nearest Neighbor
    STROKE_ARCS = Yes
    REPROJECTED -> GeometryExtractor
GeometryExtractor
    KIND_LONG = OGC Well Known Text
    ATTR = _geometry
    OGCVERSION = 1.1
    -> text_line (writer TEXTLINE_2)
text_line (writer TEXTLINE_2)
    attributes: text_line_data buffer
