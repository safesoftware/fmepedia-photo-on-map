FME workspace D002 - report_web_form.fmw

Parameters:
- SourceDataset_TEXTLINE = Z:\DonStuff\DemoData\2013Demos\AlertReportingSystem\2ndIteration\data\reporter_data\web_report_polygon_data.txt   # Source Text File(s)
- URL = http://demo.fmeserver.com   # Web Connection URL
- HTTP_AUTH_USERNAME = fmepedia   # Username
- HTTP_AUTH_PASSWORD =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   # Password

Readers:
- TEXTLINE_1: TEXTLINE from $(SourceDataset_TEXTLINE)

Writers:
- GOOGLEFUSIONTABLES_1: GOOGLEFUSIONTABLES in LL-WGS84

text_line (reader TEXTLINE_1)
    attributes: text_line_data buffer
    -> AttributeTrimmer
AttributeTrimmer
    SRC_ATTRS = text_line_data
    TRIM_CHARS = "
    TRIM_TO_NONE = Yes
    TRIM_TYPE = Both
    -> JSONFlattener
JSONFlattener
    RECURSIVE = Yes
    JSON_ATTR = text_line_data
    -> AttributeExposer
AttributeExposer
    ATTR_LIST = description,email,extremity,radius,title,url,wkt
    -> GeometryReplacer
GeometryReplacer
    ATTR = wkt
    KIND_LONG = OGC Well Known Text
    -> CoordinateExtractor
CoordinateExtractor
    Y_ATTR = latitude
    X_ATTR = longitude
    Z_DEFAULT = -9999
    Z_ATTR = _z
    IND = 0
    -> Reprojector
Reprojector
    DEST = TX83-C
    RASTER_CELL_SIZE = Preserve Cells
    STROKE_ARCS = Yes
    SOURCE = EPSG:4326
    INTERPOLATION_TYPE_NAME = Nearest Neighbor
    REPROJECTED -> Bufferer_2
Bufferer_2
    WIDTH = @Value(radius)
    BUFFSTYLE = CAP_ROUND
    ANGLE = 22.5
    BUFFERED -> Reprojector_2
Reprojector_2
    DEST = EPSG:4326
    RASTER_CELL_SIZE = Preserve Cells
    STROKE_ARCS = Yes
    SOURCE = TX83-C
    INTERPOLATION_TYPE_NAME = Nearest Neighbor
    REPROJECTED -> TimeStamper
TimeStamper
    FMT = XML DateTime (^Y-^m-^dT^H:^M:^S)
    TIME_ATTR = datetime
    -> StringConcatenator
StringConcatenator
    PARM_LINE = Web Report - Severity(@Value(extremity))
    VAL_ATTR = report_type
    -> StringConcatenator_3
    -> EMSLocationReport (writer GOOGLEFUSIONTABLES_1)
StringConcatenator_3
    PARM_LINE:
      {
      "report_type": "@Value(report_type)",
      "email_from": "@Value(email)",
      "url": "@Value(url)",
      "latitude": "@Value(latitude)",
      "longitude": "@Value(longitude)",
      "datetime": "@Value(datetime)",
      "subject": "@Value(title)",
      "content":"@Value(description)"
      }
    VAL_ATTR = email_content
    -> FMEServerNotifier_3
Note: Needs to post to ems_new_data_logged topic
FMEServerNotifier_3
    HTTP_UPLOAD_BODY = email_content
    HTTP_AUTH_PASSWORD = $(HTTP_AUTH_PASSWORD)
    STATUS_CODE_ATTR = _http_status_code
    TOPIC = ems_new_data_logged
    HTTP_AUTH_USERNAME = $(HTTP_AUTH_USERNAME)
    URL = $(URL)
    -> Logger_2
Logger_2 [off]
    MESSAGE = Feature is:
    MAXFEATS = 20
    MAXCOORDS = 20
EMSLocationReport (writer GOOGLEFUSIONTABLES_1)
    attributes: content text, datetime datetime, email_reporter text, report_type text, subject text, url text, latitude number, longitude number
