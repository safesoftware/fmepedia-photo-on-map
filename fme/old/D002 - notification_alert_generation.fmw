FME workspace D002 - notification_alert_generation.fmw

Parameters:
- SourceDataset_TEXTLINE = C:\Users\cvessaz\Desktop\485506796320928_73569109261376_notification_report2.json   # Source Text File(s)
- PICTURE_PATH = D:/FMEUserData/fmedpedia_demos/D002 - Alertdemo/static_maps/
- PHOTO_MAP_URL = https://www.google.com/fusiontables/DataSource?snapid=S566666MJRj
- EVENT_MAP_URL = https://www.google.com/fusiontables/DataSource?snapid=S566665NuRk
- HTTP_AUTH_USERNAME = fmepedia   # Username
- HTTP_AUTH_PASSWORD =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   # Password
- URL = http://demo.fmeserver.com   # Web Connection URL

Readers:
- TEXTLINE_1: TEXTLINE from $(SourceDataset_TEXTLINE)
- GOOGLEFUSIONTABLES_1: GOOGLEFUSIONTABLES

Writers:
- NULL_1: NULL

Note: text_line
text_line (reader TEXTLINE_1)
    attributes: text_line_data buffer
    -> JSONFlattener
JSONFlattener
    RECURSIVE = Yes
    JSON_ATTR = text_line_data
    -> AttributeExposer
AttributeExposer
    ATTR_LIST = content,datetime,email_from,latitude,longitude,report_type,subject,url
    -> 2DPointAdder
2DPointAdder
    XVALATTR = @Value(longitude)
    YVALATTR = @Value(latitude)
    -> StringConcatenator_2
StringConcatenator_2
    PARM_LINE = http://maps.google.com/maps/api/staticmap?center=@Value(latitude),@Value(longitude)&zoom=13&markers=@Value(latitude),@Value(longitude)&size=500x300&sensor=false
    VAL_ATTR = staticmapURL
    -> HTTPFetcher
HTTPFetcher
    VAL_ATTR = staticmapimage
    USE_HEADER_ENCODING = No
    USE_COOKIES = No
    STATUS_CODE_ATTR = _http_status_code
    SAVED_HEADERS_ATTR = _headers
    HTTP_AUTH_METHOD = Basic
    URL = @Value(staticmapURL)
    CONTINUE_ON_ERROR = No
    HTTP_PROXY_AUTH_METHOD = Basic
    -> UUIDGenerator
UUIDGenerator
    UUID_ATTR = _uuid
    -> StringConcatenator_3
StringConcatenator_3
    PARM_LINE = $(PICTURE_PATH)@Value(_uuid).jpg
    VAL_ATTR = filename
    -> AttributeFileWriter
AttributeFileWriter
    CHAR_ENCODING = fme-system
    FILE_NAME = @Value(filename)
    SOURCE_ATTR = staticmapimage
    -> SpatialFilter [input 1]
    -> SpatialFilter_2 [input 1]
    -> Inspector
Note: EMSActiveSubscriptions
EMSActiveSubscriptions (reader GOOGLEFUSIONTABLES_1)
    attributes: geom location, email text, request_id text, request_time text, enddate text, startdate text, twitter text, query_type text
    -> TestFilter
TestFilter
    TEST_LIST = BOOL_OP,OR,COMPOSITE_TEST,<Unused>,TEST_CLAUSE,"TEST ""@Value(query_type)"" = ""inside""",INSIDE_AREA_ALERT,BOOL_OP,OR,COMPOSITE_TEST,<Unused>,TEST_CLAUSE,"TEST ""@Value(query_type)"" = ""outside""",OUTSIDE_AREA_ALERT
    INSIDE_AREA_ALERT -> SpatialFilter [input 2]
    OUTSIDE_AREA_ALERT -> SpatialFilter_2 [input 2]
    INSIDE_AREA_ALERT -> Inspector
Inspector [off]
SpatialFilter
    USE_BOUNDING_BOX = For CANDIDATES Only
    MERGE_ATTRS = Yes
    BASE_TYPE = Single Base
    PASS_CRITERIA = Pass Against One Base
    PREDATTR = _predicate
    PREDICATES = INTERSECTS
    CURVE_BOUNDARY_RULE_PARAM = Default Rule
    PASSED -> StringConcatenator
SpatialFilter_2
    USE_BOUNDING_BOX = For CANDIDATES Only
    MERGE_ATTRS = Yes
    BASE_TYPE = Single Base
    PASS_CRITERIA = Pass Against One Base
    PREDATTR = _predicate
    PREDICATES = DISJOINT
    CURVE_BOUNDARY_RULE_PARAM = Default Rule
    PASSED -> StringConcatenator
StringConcatenator
    PARM_LINE:
      {
      email_to:@Value(email),
      email_subject: "Notification Alert - @Value(report_type)",
      email_attachment: "@Value(filename)",
      subscriber_content: "There has been a @Value(report_type) event.  The event has the following associated information: \r\nSubject:  @Value(subject) \r\n Content: @Value(content) \r\nURL: @Value(url)\r\n \r\n Map showing all photos logged is here: $(PHOTO_MAP_URL) \r\n\r\nMap showing all events logged is here: $(EVENT_MAP_URL) \r\n \r\n \r\n ----  UNSUBSCRIBE  ----- \r\n\r\nTo unsubscribe to these notifications click the link below.  \r\nhttp://beta.fmeserver.com/fmejobsubmitter/EEMS/subscription_delete.fmw?opt_servicemode=async&subscriber_id=@Value(request_id)&email_address=@Value(email) \r\n\r\n Image showing report location is attached below: \r\n\r\n",
      apple_content:"@Value(report_type) | @Value(subject)  - @Value(content) -  @Value(url) | @Value(latitude), @Value(longitude)"
      }
    VAL_ATTR = subscription_request
    -> FMEServerNotifier
    -> Logger
FMEServerNotifier
    HTTP_UPLOAD_BODY = subscription_request
    HTTP_AUTH_PASSWORD = $(HTTP_AUTH_PASSWORD)
    STATUS_CODE_ATTR = _http_status_code
    TOPIC = ems_notification_alert
    HTTP_AUTH_USERNAME = $(HTTP_AUTH_USERNAME)
    URL = $(URL)
Logger [off]
    MESSAGE = Feature is:
    MAXFEATS = 20
    MAXCOORDS = 20
