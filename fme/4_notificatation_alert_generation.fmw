FME workspace 4_notificatation_alert_generation.fmw

Parameters:
- SourceDataset_TEXTLINE = C:\Users\cvessaz\Desktop\485506796320928_73569109261376_notification_report2.json   # Source Text File(s)
- PHOTO_MAP_URL = https://www.google.com/fusiontables/embedviz?q=select+col0+from+1r0xCHrPZYDQYAp5It8pUagWUcKUOzJr5bxjIs45C&viz=MAP&h=false&lat=52.20068289553301&lng=-32.38338218204217&t=1&z=2&l=col0&y=2&tmplt=2&hml=KML
- URL = https://demos-safe-software.fmecloud.com
- REPOSITORY = Photo-On-Map   # Repository
- HTTP_AUTH_USERNAME = demo-author
- HTTP_AUTH_PASSWORD =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

Readers:
- TEXTLINE_1: TEXTLINE from $(SourceDataset_TEXTLINE)
- GOOGLEFUSIONTABLES_1: GOOGLEFUSIONTABLES

Writers:
- NULL_1: NULL

Note: text_line
text_line (reader TEXTLINE_1)
    attributes: text_line_data buffer
    -> JSONFlattener
2DPointAdder
    YVALATTR = @Value(latitude)
    XVALATTR = @Value(longitude)
    -> StringConcatenator_2
PhotoOnMapActiveSubscriptions (reader GOOGLEFUSIONTABLES_1)
    attributes: email text, enddate text, request_id text, request_time text, startdate text, twitter text, query_type text, geom location
    -> TestFilter
TestFilter
    DEFAULT_VALUE = <UNFILTERED>
    TEST_LIST = BOOL_OP,OR,COMPOSITE_TEST,<Unused>,TEST_CLAUSE,"TEST ""@Value(query_type)"" = ""inside""",INSIDE_AREA_ALERT,BOOL_OP,OR,COMPOSITE_TEST,<Unused>,TEST_CLAUSE,"TEST ""@Value(query_type)"" = ""outside""",OUTSIDE_AREA_ALERT
    INSIDE_AREA_ALERT -> SpatialFilter [input 2]
    OUTSIDE_AREA_ALERT -> SpatialFilter_2 [input 2]

Bookmark: Extract JSON
JSONFlattener
    RECURSIVE = Yes
    JSON_ATTR = text_line_data
    -> AttributeExposer
AttributeExposer
    ATTR_LIST = content,datetime,email_from,latitude,longitude,report_type,subject,url
    -> 2DPointAdder

Bookmark: Generate static map
StringConcatenator_2
    PARM_LINE = http://maps.google.com/maps/api/staticmap?center=@Value(latitude),@Value(longitude)&zoom=13&markers=@Value(latitude),@Value(longitude)&size=500x300&sensor=false
    VAL_ATTR = staticmapURL
    -> HTTPFetcher
HTTPFetcher
    STATUS_CODE_ATTR = _http_status_code
    SAVED_HEADERS_ATTR = _headers
    HTTP_PROXY_AUTH_METHOD = Basic
    HTTP_AUTH_METHOD = Basic
    CONTINUE_ON_ERROR = No
    VAL_ATTR = staticmapimage
    USE_COOKIES = No
    URL = @Value(staticmapURL)
    USE_HEADER_ENCODING = No
    -> UUIDGenerator
UUIDGenerator
    UUID_ATTR = _uuid
    -> StringConcatenator_3
StringConcatenator_3
    PARM_LINE = @Value(_uuid).jpg
    VAL_ATTR = filename
    -> AttributeCreator
AttributeCreator
    ATTR_LIST = filename,$(FME_SHAREDRESOURCE_TEMP)@Value(filename)
    -> AttributeFileWriter_2
AttributeFileWriter_2
    SOURCE_ATTR = staticmapimage
    OVERWRITE_FILE = Overwrite file
    FILE_NAME = @Value(filename)
    CHAR_ENCODING = fme-binary
    -> SpatialFilter_2 [input 1]
    -> SpatialFilter [input 1]

Bookmark: Trigger when report overlaps area of interest
SpatialFilter
    PREDICATES = INTERSECTS
    CURVE_BOUNDARY_RULE_PARAM = Default Rule
    USE_BOUNDING_BOX = For CANDIDATES Only
    PREDATTR = _predicate
    MERGE_ATTRS = Yes
    PASS_CRITERIA = Pass Against One Base
    BASE_TYPE = Single Base
    PASSED -> FMEServerEmailGenerator

Bookmark: Trigger when report is outside area of interest
SpatialFilter_2
    PREDICATES = DISJOINT
    CURVE_BOUNDARY_RULE_PARAM = Default Rule
    USE_BOUNDING_BOX = For CANDIDATES Only
    PREDATTR = _predicate
    MERGE_ATTRS = Yes
    PASS_CRITERIA = Pass Against One Base
    BASE_TYPE = Single Base
    PASSED -> FMEServerEmailGenerator

Bookmark: Send Confirmation Email
FMEServerEmailGenerator
    email_subscriber_content:
      <b>There has been a new photo in the area you subscribed to.</b>

      <p>The event has the following associated information:</p>

      <ul>
      <li>Subject:  @Value(subject)</li>
      <li>Content: @Value(content)</li>
      <li><a href="@Value(url)">Image URL</a></li>
      </ul>

      <p>Map showing all photos logged is <a href="$(PHOTO_MAP_URL)">here.</a></p>

      <p>Image showing report location is attached below.</p>

      ----  UNSUBSCRIBE  -----

      <p>To unsubscribe to these notifications click the link below.</p>

      $(URL)/fmejobsubmitter/$(REPOSITORY)/subscription_delete.fmw?opt_servicemode=async&subscriber_id=@Value(request_id)&email_address=@Value(email)
    email_subject = Notification Alert - @Value(report_type)
    email_attachment_paths = @Value(filename)
    email_to = @Value(email)
    -> FMEServerNotifier_2
FMEServerNotifier_2
    TOPIC = photo-map-notification-alert
    URL = $(URL)
    USERNAME = $(HTTP_AUTH_USERNAME)
    BODY = @Value(text_line_data)
    PASSWORD = $(HTTP_AUTH_PASSWORD)

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_to =   # To
- email_cc =   # CC
- email_from =   # From
- email_replyto =   # Reply to
- email_subject =   # Subject
- email_subscriber_content =   # Message
- email_attachment_paths =   # Attachments (comma separated)

INPUT (input)
    -> Counter
Counter
    SCOPE = Local
    START = 0
    DOMAIN = counter
    CNT_ATTR = _email_feature_id
    -> ParameterFetcher
ParameterFetcher
    ATTR_LIST = _email_from {$(email_from)} _email_replyto {$(email_replyto)} _email_attachment_paths {$(email_attachment_paths)} _email_cc {$(email_cc)}
    -> AttributeCreator
AttributeCreator
    NUM_PRIOR_FEATURES = 0
    NUM_SUBSEQUENT_FEATURES = 0
    ATTR_LIST = _email_to,$(email_to),_email_subject,$(email_subject),_email_subscriber_content,$(email_subscriber_content)
    -> JSONTemplater
JSONTemplater
    VISIBLE_QUERY_VALIDATE = Yes
    RESULT_ATTRIBUTE = text_line_data
    CONSECUTIVE_GROUPS = No
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    -> Tester
Tester
    BOOL_OP = OR
    TEST_DESCRIPTION = ""
    TEST_CLAUSE = TEST _email_attachment_paths ATTRIBUTE_IS_EMPTY <Unused>
    TEST_MODE = Automatic
    PASSED -> OUTPUT (output)
    FAILED -> AttributeSplitter
OUTPUT (output)

Bookmark: Add the attachments
AttributeSplitter
    ATTR_NAME = _email_attachment_paths
    TRIM_OPTION = Both
    DROP_EMPTY_PARTS = No
    DELIMITER = ,
    LIST_NAME = _email_attachment_path_list
    -> ListExploder
ListExploder
    INDEX_ATTR = _element_index
    MODE = List Elements and Original Attributes
    LIST_ATTR = _email_attachment_path_list{}
    LIST_FOUND -> StringConcatenator
StringConcatenator
    PARM_LINE = "email_attachment{@Value(_element_index)}": "@Value(_email_attachment_path_list)"
    VAL_ATTR = _email_attachment_json
    -> Aggregator
Aggregator
    ORDERED = No
    MODE = Assemble One Level
    GROUP_BY = _email_feature_id
    ACCUM_ATTRS_NAME = Yes
    SEP = ,
    AGGREGATE_TYPE = Homogeneous Collection (If Possible)
    CONCAT_ATTRS = _email_attachment_json
    AGGREGATE -> StringReplacer_2
StringReplacer_2
    FIND_TEXT = \
    NO_MATCH = _FME_NO_OP_
    REGEXP = no
    REPLACE_TEXT = \\
    CASE = no
    SRC_ATTRS = _email_attachment_json
    -> StringReplacer
StringReplacer
    FIND_TEXT = }
    NO_MATCH = _FME_NO_OP_
    REGEXP = no
    REPLACE_TEXT:
      ,
      @Value(_email_attachment_json)
      }
    CASE = no
    SRC_ATTRS = text_line_data
    -> OUTPUT (output)
