FME workspace 3_report_photo_new.fmw

Parameters:
- SourceDataset_TEXTLINE = $(FME_MF_DIR)photo-incoming.txt   # Source Text File(s)
- URL = https://demos-safe-software.fmecloud.com   # Web Connection URL
- HTTP_AUTH_USERNAME = demo-author   # Username
- HTTP_AUTH_PASSWORD =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   # Password
- PHOTO_MAP_URL = https://www.google.com/fusiontables/embedviz?q=select+col0+from+1r0xCHrPZYDQYAp5It8pUagWUcKUOzJr5bxjIs45C&viz=MAP&h=false&lat=39.858915797703546&lng=-104.67342124454217&t=1&z=20&l=col0&y=2&tmplt=2&hml=KML   # Photo Map URL
- TOKEN = 8be243c0fc2f5f34977050bdab57ebbdd3e72aa2
- FME_SHAREDRESOURCE_TEMP =   # FME Server Sharedresource Temp
- FME_SHAREDRESOURCE_DATA =   # FME Server Sharedresource Data

Readers:
- TEXTLINE_1: TEXTLINE from $(SourceDataset_TEXTLINE)

Writers:
- GOOGLEFUSIONTABLES_1: GOOGLEFUSIONTABLES

text_line (reader TEXTLINE_1)
    attributes: text_line_data buffer
    -> JSONFlattener
URLBuilder: StringConcatenator
    PARM_LINE = $(URL)/fmerest/v2/resources/FME_SHAREDRESOURCE_DATA/filesys/Photos/@Value(random_photo_folder)/@Value(file_name_only)?accept=contents&token=$(TOKEN)&disposition=attachment
    VAL_ATTR = url_of_photo
    -> TimeStamper
    -> FMEServerEmailGenerator_2
    -> AttributeRenamer_2
AttributeRenamer_2
    ATTR_LIST = jpeg_exif_make,make,"",jpeg_exif_model,model,"",jpeg_exif_gpsaltitude,altitude,"",email_subject,subject,""
    -> VertexCreator
VertexCreator
    MODE_NAME = Replace with Point
    XVAL = @Value(longitude)
    YVAL = @Value(latitude)
    -> CoordinateSystemSetter
CoordinateSystemSetter
    COORDSYS = LL84
    -> PhotoOnMapPhotoLibrary (writer GOOGLEFUSIONTABLES_1)
Note: PhotoOnMapPhotoLibrary
PhotoOnMapPhotoLibrary (writer GOOGLEFUSIONTABLES_1)
    attributes: make text, model text, url_of_photo text, latitude number, longitude number, altitude number, subject text
HTTPMultipartUploader
    AUTH_METHOD = Basic
    PROXY_AUTH_METHOD = Basic
    TARGET_ATTR = _url_contents
    RESPONSE_HEADER_LIST_ATTR = _headers
    STATUS_CODE_ATTR = _http_status_code
    ERROR_ATTR = _error
    FOLLOW_REDIRECTS = Yes
    USE_COOKIES = No
    VERIFY_SSL_CERTIFICATES = Yes
    UPLOAD_METHOD = POST
    MULTIPART_FORM_DATA_FILE = @Value(file_name_only) @Value(email_attachment)
    TARGET_URL = $(URL)/fmerest/v2/resources/FME_SHAREDRESOURCE_DATA/filesys/Photos/@Value(random_photo_folder)?createDirectories=true&detail=low&overwrite=false&token=$(TOKEN)
    -> HTTPFileUploader_Output
    <REJECTED> -> HTTPFileUploader_Output
HTTPFileUploader_Output: Logger
    MESSAGE = Feature is:
    MAXFEATS = 20
    MAXCOORDS = 20

Bookmark: Flatten JSON to get all attributes
JSONFlattener
    JSON_ATTR = text_line_data
    RECURSIVE = Yes
    -> AttributeExposer_3
AttributeExposer_3
    ATTR_LIST = email_publisher_attachment{},email_publisher_to,email_publisher_received,email_publisher_subject,email_publisher_from,email_publisher_sent,email_publisher_content
    -> AttributeRenamer
AttributeRenamer
    ATTR_LIST = email_publisher_attachment{0},email_attachment,"",email_publisher_content,email_content,"",email_publisher_from,email_from,"",email_publisher_received,email_recieved,"",email_publisher_sent,email_sent,"",email_publisher_subject,email_subject,"",email_publisher_to,email_to,""
    -> FilenamePartExtractor

Bookmark: Grab the photo name
FilenamePartExtractor
    SRC_ATTR = email_attachment
    TGT_ATTR = file_name_only
    FILENAME_PART = Full Filename
    -> RasterReader_2
RasterReader_2
    VISIBLE_READER_TYPE = JPEG (Joint Photographic Experts Group)
    DATASET = @Value(email_attachment)
    CONTINUE_ON_READER_ERROR = No
    RASTER -> UUIDGenerator
UUIDGenerator
    UUID_ATTR = random_photo_folder
    -> AttributeExposer
AttributeCopier
    ATTR_LIST = email_attachment,email_attachment_original,
    -> AttributeClassifier

Bookmark: Expose All Attributes from the Raster
AttributeExposer
    ATTR_LIST = jpeg_exif_make,jpeg_exif_model,jpeg_exif_gpslatitude,jpeg_exif_gpslatituderef,jpeg_exif_gpslongitude,jpeg_exif_gpslongituderef,jpeg_exif_aperturevalue,jpeg_exif_colorspace,jpeg_exif_componentsconfiguration,jpeg_exif_datetime,jpeg_exif_datetimedigitized,jpeg_exif_datetimeoriginal,jpeg_exif_exifversion,jpeg_exif_pixelxdimension,jpeg_exif_pixelydimension,jpeg_exif_software,jpeg_type,jpeg_exif_aperturevalue,jpeg_exif_exposuremode,jpeg_exif_exposureprogram,jpeg_exif_exposuretime,jpeg_exif_flash,jpeg_exif_flashpixversion,jpeg_exif_fnumber,jpeg_exif_focallength,jpeg_exif_focallengthin35mmfilm,jpeg_exif_gpsaltitude,jpeg_exif_gpsaltituderef,jpeg_exif_gpsimgdirection,jpeg_exif_gpsimgdirectionref,jpeg_exif_gpstimestamp,jpeg_exif_isospeedratings,jpeg_exif_meteringmode,jpeg_exif_orientation,jpeg_exif_resolutionunit,jpeg_exif_scenecapturetype,jpeg_exif_sensingmethod,jpeg_exif_sharpness,jpeg_exif_shutterspeedvalue,jpeg_exif_whitebalance,jpeg_exif_xresolution,jpeg_exif_ycbcrpositioning,jpeg_exif_yresolution
    -> AttributeCopier

Bookmark: is the photo Geotagged?
AttributeClassifier
    SRC_ATTR = jpeg_exif_gpslatitude
    CLASS = ASCII
    FAILED -> FMEServerEmailGenerator
    PASSED -> AttributeValueMapper

Bookmark: Trigger Failure Email to User
FMEServerEmailGenerator
    email_to = @Value(email_from)
    email_subject = Your request FAILED!
    email_subscriber_content = Your photo was taken by: @Value(jpeg_exif_make), @Value(jpeg_exif_model).  This service failed as it only accepts photos that are geotagged.
    -> FMEServerNotifier_4
FMEServerNotifier_4
    USERNAME = $(HTTP_AUTH_USERNAME)
    PASSWORD = $(HTTP_AUTH_PASSWORD)
    TOPIC = photo_map_report
    BODY = @Value(text_line_data)
    URL = $(URL)

Bookmark: Rotate Image If Needed
AttributeValueMapper
    LUT = 1,0,3,180,6,-90,8,90
    SRC = jpeg_exif_orientation
    DIRECTION = Forward (Source To Destination)
    VAL_ATTR = _rotation
    DEFAULT_VALUE = 0
    -> TestFilter
TestFilter
    DEFAULT_VALUE = <UNFILTERED>
    TEST_LIST = BOOL_OP,OR,COMPOSITE_TEST,<Unused>,TEST_CLAUSE,"TEST ""@Value(_rotation)"" != ""0""",Rotation Needed
    Rotation Needed -> Rotator_2
    <UNFILTERED> -> AttributeSplitter
Rotator_2
    XORIG = 0
    ANGLE = @Value(_rotation)
    YORIG = 0
    ROTATED -> RasterRotationApplier
RasterRotationApplier
    INTERPOLATION_TYPE_NAME = Bilinear
    -> RasterExtractor
RasterExtractor
    RASTER_FORMAT_ATTR = _rasterFormatName
    RASTER_FORMAT = JPEG (Joint Photographic Experts Group)
    RASTER_BLOB_ATTR = _rasterBlob
    -> AttributeCreator
AttributeCreator
    ATTR_LIST = email_attachment,$(FME_SHAREDRESOURCE_TEMP)@Value(file_name_only)
    -> AttributeFileWriter
AttributeFileWriter
    FILE_NAME = @Value(email_attachment)
    OVERWRITE_FILE = Overwrite file
    CHAR_ENCODING = fme-binary
    SOURCE_ATTR = _rasterBlob
    -> AttributeRemover
AttributeRemover
    REMOVE_ATTRS = _rasterBlob
    -> AttributeSplitter

Bookmark: Build Latitude
AttributeSplitter
    DELIMITER = " "
    TRIM_OPTION = Both
    DROP_EMPTY_PARTS = No
    LIST_NAME = _latlist
    ATTR_NAME = jpeg_exif_gpslatitude
    -> AttributeTrimmer
AttributeTrimmer
    TRIM_TYPE = Both
    TRIM_CHARS = ()
    SRC_ATTRS = _latlist{0},_latlist{1},_latlist{2}
    TRIM_TO_NONE = Yes
    -> AttributeCreator_2
AttributeCreator_2
    ATTR_LIST = latitude,@Evaluate(@Value(_latlist{0})+(@Value(_latlist{1})/60.0)+(@Value(_latlist{2})/3600.0))
    -> Tester
Tester
    TEST_DESCRIPTION = ""
    TEST_MODE = Automatic
    TEST_CLAUSE = TEST "@Value(jpeg_exif_gpslatituderef)" != "N"
    BOOL_OP = OR
    PASSED -> AttributeCreator_4
    FAILED -> AttributeSplitter_2
AttributeCreator_4
    ATTR_LIST = latitude,-@Value(latitude)
    -> AttributeSplitter_2

Bookmark: Build Longitude
AttributeSplitter_2
    DELIMITER = " "
    TRIM_OPTION = Both
    DROP_EMPTY_PARTS = No
    LIST_NAME = _longlist
    ATTR_NAME = jpeg_exif_gpslongitude
    -> AttributeTrimmer_2
AttributeTrimmer_2
    TRIM_TYPE = Both
    TRIM_CHARS = ()
    SRC_ATTRS = _longlist{0},_longlist{1},_longlist{2}
    TRIM_TO_NONE = Yes
    -> AttributeCreator_3
AttributeCreator_3
    ATTR_LIST = longitude,@Evaluate(@Value(_longlist{0})+(@Value(_longlist{1})/60.0)+(@Value(_longlist{2})/3600.0))
    -> Tester_2
Tester_2
    TEST_DESCRIPTION = ""
    TEST_MODE = Automatic
    TEST_CLAUSE = TEST "@Value(jpeg_exif_gpslongituderef)" = "W"
    BOOL_OP = OR
    PASSED -> AttributeCreator_5
    FAILED -> 2DPointReplacer
AttributeCreator_5
    ATTR_LIST = longitude,-@Value(longitude)
    -> 2DPointReplacer
2DPointReplacer
    YVALATTR = @Value(latitude)
    XVALATTR = @Value(longitude)
    POINT -> AttributeTrimmer_3

Bookmark: BuildAltitude
AttributeTrimmer_3
    TRIM_TYPE = Both
    TRIM_CHARS = ()
    SRC_ATTRS = jpeg_exif_gpsaltitude
    TRIM_TO_NONE = Yes
    -> URLBuilder
    -> HTTPMultipartUploader

Bookmark: Trigger Success Email to User
FMEServerEmailGenerator_2
    email_to = @Value(email_from)
    email_subject = Your request succeeded!
    email_subscriber_content:
      Thanks for submitting your photo to the demo system!<br>

      <p>Your photo has been added to the catalog. To see the photo on a map go <a href="$(PHOTO_MAP_URL)">here</a>. A red pin indicates a location of a photo. Click on that to see a thumbnail and a link to the complete photo.</p>
    -> FMEServerNotifier_2
FMEServerNotifier_2
    USERNAME = $(HTTP_AUTH_USERNAME)
    PASSWORD = $(HTTP_AUTH_PASSWORD)
    TOPIC = photo_map_report
    BODY = @Value(text_line_data)
    URL = $(URL)

Bookmark: Trigger Downstream Event - photo_map_new_data_logged
TimeStamper
    TIME_ATTR = datetime
    FMT = XML DateTime (^Y-^m-^dT^H:^M:^S)
    -> StringConcatenator_3
StringConcatenator_3
    PARM_LINE:
      {
      "report_type": "photo",
      "email_from": "@Value(email_from)",
      "url": "@Value(url_of_photo)",
      "latitude": "@Value(latitude)",
      "longitude": "@Value(longitude)",
      "datetime": "@Value(datetime)",
      "subject": "@Value(email_subject)",
      "content":"@Value(email_content)"
      }
    VAL_ATTR = email_content
    -> FMEServerNotifier
FMEServerNotifier
    USERNAME = $(HTTP_AUTH_USERNAME)
    PASSWORD = $(HTTP_AUTH_PASSWORD)
    TOPIC = photo_map_new_data_logged
    BODY = @Value(email_content)
    URL = $(URL)

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_to =   # To
- email_cc =   # CC
- email_from =   # From
- email_replyto =   # Reply to
- email_subject =   # Subject
- email_subscriber_content =   # Message
- email_attachment_paths =   # Attachments (comma separated)

INPUT (input)
    -> Counter
Counter
    SCOPE = Local
    START = 0
    DOMAIN = counter
    CNT_ATTR = _email_feature_id
    -> ParameterFetcher
ParameterFetcher
    ATTR_LIST = _email_from {$(email_from)} _email_replyto {$(email_replyto)} _email_attachment_paths {$(email_attachment_paths)} _email_cc {$(email_cc)}
    -> AttributeCreator
AttributeCreator
    ATTR_LIST = _email_to,$(email_to),_email_subject,$(email_subject),_email_subscriber_content,$(email_subscriber_content)
    NUM_PRIOR_FEATURES = 0
    NUM_SUBSEQUENT_FEATURES = 0
    -> JSONTemplater
JSONTemplater
    CONSECUTIVE_GROUPS = No
    RESULT_ATTRIBUTE = text_line_data
    VISIBLE_QUERY_VALIDATE = Yes
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    -> Tester
Tester
    TEST_DESCRIPTION = ""
    TEST_MODE = Automatic
    TEST_CLAUSE = TEST _email_attachment_paths ATTRIBUTE_IS_EMPTY <Unused>
    BOOL_OP = OR
    PASSED -> OUTPUT (output)
    FAILED -> AttributeSplitter
OUTPUT (output)

Bookmark: Add the attachments
AttributeSplitter
    DELIMITER = ,
    TRIM_OPTION = Both
    DROP_EMPTY_PARTS = No
    LIST_NAME = _email_attachment_path_list
    ATTR_NAME = _email_attachment_paths
    -> ListExploder
ListExploder
    INDEX_ATTR = _element_index
    MODE = List Elements and Original Attributes
    LIST_ATTR = _email_attachment_path_list{}
    LIST_FOUND -> StringConcatenator
StringConcatenator
    PARM_LINE = "email_attachment{@Value(_element_index)}": "@Value(_email_attachment_path_list)"
    VAL_ATTR = _email_attachment_json
    -> Aggregator
Aggregator
    MODE = Assemble One Level
    ORDERED = No
    AGGREGATE_TYPE = Homogeneous Collection (If Possible)
    CONCAT_ATTRS = _email_attachment_json
    GROUP_BY = _email_feature_id
    SEP = ,
    ACCUM_ATTRS_NAME = Yes
    AGGREGATE -> StringReplacer_2
StringReplacer_2
    CASE = no
    REPLACE_TEXT = \\
    SRC_ATTRS = _email_attachment_json
    FIND_TEXT = \
    REGEXP = no
    NO_MATCH = _FME_NO_OP_
    -> StringReplacer
StringReplacer
    CASE = no
    REPLACE_TEXT:
      ,
      @Value(_email_attachment_json)
      }
    SRC_ATTRS = text_line_data
    FIND_TEXT = }
    REGEXP = no
    NO_MATCH = _FME_NO_OP_
    -> OUTPUT (output)
